# SUBSET-026-3 v330_extract_chap_3_5
/ReX_Import/imported modules/SUBSET-026-3 v330_extract_chap_3_5

# Specification
- Description: Subsection 26, Chapter 3.5

## R169 (Requirement Type)

### R95 (Requirement Type)
Management of Radio Communication
- Section: 3.5

### R6 (Requirement Type)
Note: the following section refers to the behaviour of the user application interacting with Euroradio protocols. How the messages are actually transported from the sender to the receiver user application is not relevant for this description.
- Section: 3.5.1.1

### R58 (Requirement Type)
General
- Section: 3.5.2

### R11 (Requirement Type)
Each communication session managed by an entity shall allow the exchange of data with only one other entity.
- Section: 3.5.2.1
- Event-B Link Type -> R199

### R29 (Requirement Type)
Note: in the following sections reference is made to safe radio connections, whose definition and management is contained in Euroradio specification.
- Section: 3.5.2.2

### R164 (Requirement Type)
The information Initiation of a Communication Session and Version not Compatible (see sections F3.5.3 and F Erreur ! Source du renvoi introuvable. ) shall be the same in every system version.
- Section: 3.5.2.3

### R30 (Requirement Type)
Establishing a communication session
- Section: 3.5.3

### R91 (Requirement Type)
It shall be possible for ERTMS/ETCS on-board equipment and RBC to initiate a communication session.
- Section: 3.5.3.1
- Event-B Link Type -> R200
- Event-B Link Type -> R201
- Event-B Link Type -> R202

### R93 (Requirement Type)
A Radio Infill Unit (see section F Erreur ! Source du renvoi introuvable. ) shall never initiate a communication session.
- Section: 3.5.3.2
- Event-B Link Type -> R201

### R53 (Requirement Type)
Note: Only communication sessions between an ERTMS/ETCS on-board equipment and a trackside equipment (RBC or Radio Infill Unit) are considered here.
- Section: 3.5.3.3

### R139 (Requirement Type)
The on-board shall establish a communication session
- Section: 3.5.3.4

### R49 (Requirement Type)
a)At Start of Mission (only if level 2 or 3).
- Event-B Link Type -> R198

### R152 (Requirement Type)
b)If ordered from trackside.
- Event-B Link Type -> R196
- Event-B Link Type -> R197

### R63 (Requirement Type)
c)If a mode change, not considered as an End of Mission, has to be reported to the RBC (only if level 2 or 3)
- Event-B Link Type -> R195

### R25 (Requirement Type)
d)If the driver has manually changed the level to 2 or 3
- Event-B Link Type -> R194

### R5 (Requirement Type)
e)When the train front reaches the end of an announced radio hole
- Event-B Link Type -> R193

### R148 (Requirement Type)
f)When the previous communication session is considered as terminated due to loss of safe radio connection (refer to 3.5.4.2.1)
- Event-B Link Type -> R192

### R85 (Requirement Type)
g)When a Start of Mission procedure, during which no communication session could be established, is completed in level 2 or 3

### R134 (Requirement Type)
In respect of a), b), c), d) and e) of 3.5.3.4, the on-board shall not establish a new communication session with an RBC/RIU in case a communication session is currently being established or is already established with this RBC/RIU.
- Section: 3.5.3.4.1

### R185 (Requirement Type)
The order to contact an RBC shall include
- Section: 3.5.3.5

### R35 (Requirement Type)
a)The identity of the RBC.

### R22 (Requirement Type)
b)The telephone number of the RBC.

### R137 (Requirement Type)
c)The action to be performed (establish/terminate the session).

### R3 (Requirement Type)
d)Whether this applies also to Sleeping units.

### R135 (Requirement Type)
See table at the end of section 3.5.3.
- Section: 3.5.3.5.1

### R98 (Requirement Type)
If the ERTMS/ETCS on-board equipment has to establish a communication session with an RBC whilst in session with another RBC, the existing communication session shall be terminated (see 3.5.5.2 for details) and the new one shall be established. Exception: the order to contact an Accepting RBC shall not terminate the communication session with the Handing Over RBC.
- Section: 3.5.3.5.2
- Event-B Link Type -> R203

### R24 (Requirement Type)
The order to contact an Accepting RBC shall be part of the RBC transition order and shall include:
- Section: 3.5.3.5.3

### R120 (Requirement Type)
a)The identity of the Accepting RBC.

### R4 (Requirement Type)
b)The telephone number of the Accepting RBC.

### R34 (Requirement Type)
c)Whether this applies also to Sleeping unit.

### R182 (Requirement Type)
The order to contact a Radio Infill Unit shall include
- Section: 3.5.3.6

### R151 (Requirement Type)
a)The identity of the Radio Infill Unit

### R163 (Requirement Type)
b)The telephone number of the Radio Infill Unit

### R132 (Requirement Type)
c)The action to be performed (establish/terminate the session).

### R26 (Requirement Type)
If the establishment of a communication session is initiated by the on-board, it shall be performed according to the following steps:
- Section: 3.5.3.7

### R54 (Requirement Type)
a)The on-board shall request the set-up of a safe radio connection with the trackside. If this request is part of an on-going Start of Mission procedure, it shall be repeated until successful or a defined number of times (see Appendix A3.1).
- Event-B Link Type -> R212

### R177 (Requirement Type)
If this request is not part of an on-going Start of Mission procedure, it shall be repeated until at least one of the following conditions is met:

### R20 (Requirement Type)
•Safe radio connection is set up
- Event-B Link Type -> R213

### R156 (Requirement Type)
•End of Mission is performed
- Event-B Link Type -> R204

### R140 (Requirement Type)
•Order to terminate communication session is received from trackside
- Event-B Link Type -> R215

### R103 (Requirement Type)
•The train passes a level transition border (from level 2/3 to level 0, NTC, 1) with its front end.
- Event-B Link Type -> R207

### R17 (Requirement Type)
•Order to establish communication session with a different RBC is received from trackside and the order does not request to contact an Accepting RBC.
- Event-B Link Type -> R209

### R113 (Requirement Type)
•The train passes a RBC/RBC border with its front end.
- Event-B Link Type -> R208

### R19 (Requirement Type)
•The train front passes the start of an announced radio hole
- Event-B Link Type -> R206

### R52 (Requirement Type)
•Regards RIUs only: Level 1 is left
- Event-B Link Type -> R205

### R9 (Requirement Type)
A request shall be repeated immediately after EURORADIO has indicated that setting up the safe radio connection has failed.

### R87 (Requirement Type)
b)As soon as the safe radio connection is set-up, the on-board shall send the message Initiation of communication session to the trackside.

### R144 (Requirement Type)
c)As soon as the trackside receives the information, it shall send the system version.

### R79 (Requirement Type)
When the on-board receives the system version it shall consider the communication session established and:
- Section: 3.5.3.8

### R67 (Requirement Type)
a)If one of its supported system versions is compatible with the one sent by trackside, it shall send a session established report, including its telephone numbers, to the trackside.
- Event-B Link Type -> R211

### R72 (Requirement Type)
b)If none of its supported system versions is compatible with the one sent by trackside, it shall send a version independent message indicating “No compatible version supported”. It shall inform the driver and shall terminate the communication session.
- Event-B Link Type -> R210

### R64 (Requirement Type)
When the trackside receives the session established report or the information that no compatible system version is supported by the on-board, it shall consider the communication session established.
- Section: 3.5.3.9

### R131 (Requirement Type)
Intentionally deleted.
- Section: 3.5.3.9.1

### R162 (Requirement Type)
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
### R105 (Requirement Type)
Figure
F1
: Establishment initiated by on-board

### R125 (Requirement Type)
If the establishment of a communication session is initiated by the RBC, it shall be performed according to the following steps:
- Section: 3.5.3.10

### R80 (Requirement Type)
a)The trackside shall request the set-up of a safe radio connection with the on-board.

### R188 (Requirement Type)
b)As soon as the safe radio connection is set-up, the trackside shall send the message Initiation of communication session to the on-board.

### R32 (Requirement Type)
c)When the on-board receives the information, it shall consider the communication session established and send a session established report to the trackside.
- Event-B Link Type -> R214

### R154 (Requirement Type)
d)When the trackside receives the session established report, it shall consider the communication session established.

### R167 (Requirement Type)
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
### R96 (Requirement Type)
Figure
F2
: Establishment initiated by the RBC

### R1 (Requirement Type)
In case the RBC is the initiator, the first message from RBC to on-board shall have the time-stamp and the LRBG identity set to "unknown".
- Section: 3.5.3.11

### R104 (Requirement Type)
Note: In the case the RBC is the initiator, there is no need to verify the compatibility of the system versions and for the on-board to send its telephone numbers, because the on-board is obviously already known to the RBC.
- Section: 3.5.3.12

### R157 (Requirement Type)
An order to contact the RBC may contain a special value for the RBC identity indicating that the on-board shall contact the last known RBC (i.e., using the stored RBC ID/phone number, if any); the phone number indicated in the order shall be ignored by the on-board equipment.
- Section: 3.5.3.13

### R36 (Requirement Type)
If there is no RBC ID/ phone number stored on-board, the order to contact the RBC shall be ignored.
- Section: 3.5.3.13.1

### R166 (Requirement Type)
Note: If a short number is used (considering trackside call routing), that number can be programmed into the balise instead of the normal phone number.
- Section: 3.5.3.14

### R153 (Requirement Type)
An order to contact the RBC may contain a special value for the RBC phone number indicating that the on-board shall use the on-board short number.
- Section: 3.5.3.15

### R70 (Requirement Type)
Note: The on-board stored short number for calling the RBC is defined by EIRENE.
- Section: 3.5.3.15.1

### R183 (Requirement Type)
- Section: 3.5.3.16

### R114 (Requirement Type)
| Option | Balise data content | Train reaction |
| --- | --- | --- |
| 1 |  | Contact last known RBC (order is ignored in case no RBC ID/ phone number is stored on-board) |
| 2 |  |  |
| 3 |  | Contact given RBC by using RBC ID and the RBC phone number |
| No Connection |  |  |
|  |  | Connection Up |
| Condition Id | Content of the conditions |  |
| [1] | (a Start of mission procedure is on-going) AND (the final attempt to set-up the safe radio connection failed) |  |
| [2] | (the “connection status” timer expires) |  |
| [3] | (no Start of mission procedure is on-going) AND (the requests to set-up a safe radio connection are stopped with the relevant RBC/RIU for reason other than the successful set-up) |  |
| [4] | (the safe radio connection is set-up) |  |
| [5] | (the safe radio connection is released) |  |
| [6] | (the safe radio connection is lost) AND (the requests to set-up a safe radio connection are stopped with the relevant RBC/RIU for reason other than the successful set-up) |  |
| [7] | (the safe radio connection is lost) AND (the train front is inside an announced radio hole) |  |

#### R138 (Requirement Type)

##### R172 (Requirement Type)
Option

##### R65 (Requirement Type)
Balise data content

##### R12 (Requirement Type)
Train reaction

#### R14 (Requirement Type)

##### R168 (Requirement Type)
- Section: 1

##### R142 (Requirement Type)
Order to contact RBC
Special value for RBC ID:
Contact last known RBC
RBC Phone number irrelevant

##### R107 (Requirement Type)
Contact last known RBC (order is ignored in case no RBC ID/ phone number is stored on-board)

#### R146 (Requirement Type)

##### R170 (Requirement Type)
- Section: 2

##### R100 (Requirement Type)
Order to contact RBC
RBC ID
Special value for RBC phone number: use on-board stored short number

##### R119 (Requirement Type)
Contact given RBC by using RBC ID and the on-board short number.
Note: If the short number does not direct to the RBC with the given RBC ID, the connection will be terminated (EURORADIO functionality).

#### R175 (Requirement Type)

##### R2 (Requirement Type)
- Section: 3

##### R73 (Requirement Type)
Order to contact RBC
RBC ID + RBC phone number

##### R136 (Requirement Type)
Contact given RBC by using RBC ID and the RBC phone number

### R88 (Requirement Type)
Maintaining a communication session
- Section: 3.5.4

### R176 (Requirement Type)
When a communication session is established, in case of a loss of the safe radio connection, i.e., if the disconnection has not been ordered (see 3.5.5.1), the involved entities shall consider the communication session still established for a defined time. The defined time shall start as soon as EURORADIO has indicated the loss of the safe radio connection.
- Section: 3.5.4.1

### R44 (Requirement Type)
When EURORADIO indicates the loss of the safe radio connection, the ERTMS/ETCS on-board equipment shall immediately try to set-up a new safe radio connection.
- Section: 3.5.4.2

### R16 (Requirement Type)
3.5.4.2.1If the safe radio connection is not re-established after the defined time (as defined in A3.1), both, on-board equipment and trackside, shall consider the session as terminated
.

### R121 (Requirement Type)
The attempts shall be repeated, until at least one of the following conditions is met:
- Section: 3.5.4.3

### R190 (Requirement Type)
•The safe radio connection is set-up.

### R8 (Requirement Type)
•The session is considered as terminated.

### R155 (Requirement Type)
•The train passes the location indicated in the RIU order “Terminate the communication session”

### R71 (Requirement Type)
Note: if the session is considered as terminated due to 3.5.4.2.1, the attempts will be resumed immediately according to 3.5.3.4 f).
- Section: 3.5.4.3.1

### R86 (Requirement Type)
Exception to 3.5.4.2 and 3.5.4.3: the on-board equipment shall not try to set up a new safe radio connection and shall stop any on-going attempts if the train front is inside an announced radio hole (see 3.12.1.3). The on-board equipment shall try to set it up again when the train front reaches the end of the radio hole.
- Section: 3.5.4.4

### R57 (Requirement Type)
In case a message has to be sent during the loss of the safe radio connection, this message shall be considered as sent.
- Section: 3.5.4.5

### R82 (Requirement Type)
Terminating a communication session
- Section: 3.5.5

### R75 (Requirement Type)
The termination of a communication session shall be initiated only by the on-board and in the following cases:
- Section: 3.5.5.1

### R78 (Requirement Type)
a)If an order is received from trackside (RBC, RIU or balise groups) (see sections 3.5.3.5 and 3.5.3.6 concerning the content of the order).

### R186 (Requirement Type)
b)If an error condition requiring the termination of the communication session is detected on-board (e.g., not compatible system versions between on-board and trackside).

### R145 (Requirement Type)
c)The train is rejected by RBC during Start of Mission.

### R149 (Requirement Type)
d)If the driver closes the desk during Start of Mission.

### R18 (Requirement Type)
e)In case the train has reported having exited from an RBC area and no order to terminate the session is received within a fixed waiting time (see Appendix A.3.1) from the time the position report was sent, the ERTMS/ETCS on-board equipment shall repeatedly send a position report with the fixed waiting time after each repetition, until the order to terminate the session is received, or the defined number of repetitions (see Appendix A.3.1) has been reached. If no reply is received within the fixed waiting time after the last repetition, the ERTMS/ETCS on-board equipment shall terminate the communication session.

### R130 (Requirement Type)
f)In case of communication session with an RIU: the Level 1 is left, or, an End of Mission is executed.

### R150 (Requirement Type)
In case a session is established, the on-board equipment shall terminate the communication session according to the following steps:
- Section: 3.5.5.2

### R50 (Requirement Type)
a)The on-board equipment shall send a Termination of communication session message.

### R178 (Requirement Type)
b)As soon as this information is received, the trackside shall consider the communication session terminated and send an acknowledgement to the on-board.

### R10 (Requirement Type)
c)When the acknowledgement is received the on-board shall consider the communication session terminated and request the release of the safe radio connection with trackside.

### R55 (Requirement Type)
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
### R62 (Requirement Type)
Figure
F3
: Termination of a communication session

### R48 (Requirement Type)
No further message shall be sent by the on-board after the message Termination of communication session.
- Section: 3.5.5.3

### R128 (Requirement Type)
Exception: In case a communication session is established and no acknowledgement is received within a fixed waiting time (see Appendix A.3.1) after sending the “Termination of communication session” message, the message shall be repeated with the fixed waiting time after each repetition.
- Section: 3.5.5.3.1

### R23 (Requirement Type)
After a defined number of repetitions (see Appendix A.3.1), and if no acknowledgment is received within the fixed waiting time from the time of the last sending of “Termination of communication session”, the ERTMS/ETCS onboard equipment shall consider the communication session terminated.
- Section: 3.5.5.3.2

### R165 (Requirement Type)
No further message shall be sent by the trackside after the message Acknowledgement of the termination of communication session.
- Section: 3.5.5.4

### R173 (Requirement Type)
The information Termination of Communication Session and corresponding Acknowledgement shall be the same in every system version.
- Section: 3.5.5.5

### R38 (Requirement Type)
Messages from the RBC received onboard after the message “Termination of communication session” has been sent shall be ignored with the exception of the Acknowledgement of the termination of communication session.
- Section: 3.5.5.6

### R83 (Requirement Type)
In case an order to terminate the communication session is received, while the communication session is currently being established, the on-board shall abort the process of establishing it and shall release the safe radio connection.
- Section: 3.5.5.7

### R27 (Requirement Type)
Registering to the Radio Network
- Section: 3.5.6

### R181 (Requirement Type)
ERTMS/ETCS on-board equipment shall order the registration of its connected Mobile Terminal(s) to a Radio Network:
- Section: 3.5.6.1

### R179 (Requirement Type)
a)At power-up

### R101 (Requirement Type)
b)Following driver entry of a new Radio Network identity (only if level 2 or 3)

### R123 (Requirement Type)
c)If ordered from the trackside

### R92 (Requirement Type)
When powered-off, ERTMS/ETCS on-board equipment shall memorize the last received Radio Network identity (from trackside or from driver) and shall use it when powered-up again.
- Section: 3.5.6.2

### R180 (Requirement Type)
If no Radio Network identity received from trackside or from driver could have been memorized by ERTMS/ETCS on-board equipment (e.g. after a System Failure or at very first power-up), this latter shall nevertheless order the registration of its Mobile Terminal(s) to a default Radio Network.
- Section: 3.5.6.3

### R184 (Requirement Type)
Note 1: the source used to retrieve the default Radio Network identity (on-board equipment permanent storage, Mobile Terminal itself, or other external source) is implementation dependent.
- Section: 3.5.6.3.1

### R143 (Requirement Type)
3.5.6.3.2Note 2: if ERTMS/ETCS on-board equipment is powered-up in an area not covered by the memorized or default Radio Network, attempts to register to this Radio Network will be repeated unconditionally by the Mobile Terminal(s) until either an attempt is successful or a new Radio Network identity is received from trackside or from driver, preventing Mobile Terminal(s) from registering to any unwanted Radio Network
.

### R161 (Requirement Type)
Note: for Radio Network identity data entry by driver during SoM, please refer to chapter 5 (Procedure Start of Mission).
- Section: 3.5.6.4

### R33 (Requirement Type)
On reception of the trackside order, ERTMS/ETCS on-board equipment shall immediately order the Radio Network registration of each Mobile Terminal that fulfils the following conditions:
- Section: 3.5.6.5

### R147 (Requirement Type)
a)it is not yet registered to the ordered Radio Network, AND

### R108 (Requirement Type)
b)it is not used for an established communication session, AND

### R90 (Requirement Type)
c)no safe radio connection is being set-up

### R129 (Requirement Type)
If a Mobile Terminal is not currently registered to the Radio Network ordered by trackside and if one of the conditions b) or c) is not fulfilled, ERTMS/ETCS on-board equipment shall initiate the Radio Network registration once communication session is terminated and safe radio connection is released.
- Section: 3.5.6.6

### R84 (Requirement Type)
If no Mobile Terminal is duly registered to a Radio Network, any order to contact an RBC or an RIU received from trackside shall be rejected by ERTMS/ETCS on-board equipment.
- Section: 3.5.6.7

### R118 (Requirement Type)
Safe Radio Connection Indication
- Section: 3.5.7

### R94 (Requirement Type)
The ERTMS/ETCS on-board equipment shall inform the driver about the status of the safe radio connection. To that purpose, the following indication statuses of the safe radio connection are defined: “No Connection”, “Connection Lost/Set-Up failed”, “Connection Up”.
- Section: 3.5.7.1

### R74 (Requirement Type)
In addition, the ERTMS/ETCS on-board equipment shall use a “connection status” timer (see Appendix A.3.1), in order to manage properly the transitions to the indication status “Connection Lost/Set-Up failed”.
- Section: 3.5.7.2

### R46 (Requirement Type)
Note: The purpose of the “connection status” timer is to avoid distracting the driver for any short disturbance of the safe radio connection.
- Section: 3.5.7.2.1

### R124 (Requirement Type)
The ERTMS/ETCS on-board equipment shall start the “connection status” timer as soon as the first request to set-up a safe radio connection with the relevant RBC/RIU is sent:
- Section: 3.5.7.3

### R39 (Requirement Type)
a)for what regards the session establishment, see items b), c), d), e) in 3.5.3.4.

### R115 (Requirement Type)
b)for what regards maintaining a communication session, see 3.5.4.2 and 3.5.4.4

### R47 (Requirement Type)
If the “connection status” timer is ongoing, it shall be stopped if the requests to set-up a safe radio connection are stopped with the relevant RBC/RIU.
- Section: 3.5.7.4

### R45 (Requirement Type)
The ERTMS/ETCS on-board equipment shall execute the transitions between the different indication statuses of the safe radio connection with the relevant RBC/RIU as described in FTable 1 according to the conditions in FTable 2 (see section 4.6.1 for details about the symbols).
- Section: 3.5.7.5

### R122 (Requirement Type)
| Option | Balise data content | Train reaction |
| --- | --- | --- |
| 1 |  | Contact last known RBC (order is ignored in case no RBC ID/ phone number is stored on-board) |
| 2 |  |  |
| 3 |  | Contact given RBC by using RBC ID and the RBC phone number |
| No Connection |  |  |
|  |  | Connection Up |
| Condition Id | Content of the conditions |  |
| [1] | (a Start of mission procedure is on-going) AND (the final attempt to set-up the safe radio connection failed) |  |
| [2] | (the “connection status” timer expires) |  |
| [3] | (no Start of mission procedure is on-going) AND (the requests to set-up a safe radio connection are stopped with the relevant RBC/RIU for reason other than the successful set-up) |  |
| [4] | (the safe radio connection is set-up) |  |
| [5] | (the safe radio connection is released) |  |
| [6] | (the safe radio connection is lost) AND (the requests to set-up a safe radio connection are stopped with the relevant RBC/RIU for reason other than the successful set-up) |  |
| [7] | (the safe radio connection is lost) AND (the train front is inside an announced radio hole) |  |

#### R102 (Requirement Type)

##### R126 (Requirement Type)
No Connection

##### R110 (Requirement Type)
< 3
-p2-

##### R61 (Requirement Type)
< 5, 6, 7
-p1-

#### R31 (Requirement Type)

##### R76 (Requirement Type)
1, 2 >
-p2-

##### R77 (Requirement Type)
Connection Lost /
Set-Up failed

##### R7 (Requirement Type)
<2
-p2-

#### R81 (Requirement Type)

##### R68 (Requirement Type)
4 >
-p1-

##### R15 (Requirement Type)
4 >
-p1-

##### R112 (Requirement Type)
Connection Up

### R51 (Requirement Type)
Table
F1
: Transitions between the indication statuses of the safe radio connection

### R159 (Requirement Type)
| Option | Balise data content | Train reaction |
| --- | --- | --- |
| 1 |  | Contact last known RBC (order is ignored in case no RBC ID/ phone number is stored on-board) |
| 2 |  |  |
| 3 |  | Contact given RBC by using RBC ID and the RBC phone number |
| No Connection |  |  |
|  |  | Connection Up |
| Condition Id | Content of the conditions |  |
| [1] | (a Start of mission procedure is on-going) AND (the final attempt to set-up the safe radio connection failed) |  |
| [2] | (the “connection status” timer expires) |  |
| [3] | (no Start of mission procedure is on-going) AND (the requests to set-up a safe radio connection are stopped with the relevant RBC/RIU for reason other than the successful set-up) |  |
| [4] | (the safe radio connection is set-up) |  |
| [5] | (the safe radio connection is released) |  |
| [6] | (the safe radio connection is lost) AND (the requests to set-up a safe radio connection are stopped with the relevant RBC/RIU for reason other than the successful set-up) |  |
| [7] | (the safe radio connection is lost) AND (the train front is inside an announced radio hole) |  |

#### R13 (Requirement Type)

##### R141 (Requirement Type)
Condition Id

##### R158 (Requirement Type)
Content of the conditions

#### R89 (Requirement Type)

##### R21 (Requirement Type)
[1]

##### R187 (Requirement Type)
(a Start of mission procedure is on-going) AND (the final attempt to set-up the safe radio connection failed)

#### R117 (Requirement Type)

##### R116 (Requirement Type)
[2]

##### R59 (Requirement Type)
(the “connection status” timer expires)

#### R40 (Requirement Type)

##### R28 (Requirement Type)
[3]

##### R109 (Requirement Type)
(no Start of mission procedure is on-going) AND (the requests to set-up a safe radio connection are stopped with the relevant RBC/RIU for reason other than the successful set-up)

#### R99 (Requirement Type)

##### R42 (Requirement Type)
[4]

##### R37 (Requirement Type)
(the safe radio connection is set-up)

#### R60 (Requirement Type)

##### R56 (Requirement Type)
[5]

##### R106 (Requirement Type)
(the safe radio connection is released)

#### R43 (Requirement Type)

##### R111 (Requirement Type)
[6]

##### R69 (Requirement Type)
(the safe radio connection is lost) AND (the requests to set-up a safe radio connection are stopped with the relevant RBC/RIU for reason other than the successful set-up)

#### R41 (Requirement Type)

##### R133 (Requirement Type)
[7]

##### R66 (Requirement Type)
(the safe radio connection is lost) AND (the train front is inside an announced radio hole)

### R174 (Requirement Type)
Table
F2
: Transition conditions for the indication statuses of the safe radio connection

### R97 (Requirement Type)
For the case of an RBC/RBC transition, the safe radio connection indicated to the driver shall switch from the indication status of the safe radio connection with the Handing over RBC to the one with the Accepting RBC as soon as one of the following conditions is met:
- Section: 3.5.7.6

### R171 (Requirement Type)
a)the ERTMS/ETCS on-board equipment sends a position report directly to the Accepting RBC with its maximum safe front end having passed the border, see 3.15.1.3.5 (i.e. the Accepting RBC becomes the supervising RBC),

### R127 (Requirement Type)
b)the safe radio connection is released with the Handing over RBC and the minimum safe rear end of the train has crossed the border, see 3.5.5.1 e) and 3.15.1.2.7.

### R189 (Requirement Type)
Note: During an RBC/RBC handover procedure, an indication status transition table and a connection status timer might have to be managed at the same time, for each RBC.
- Section: 3.5.7.6.1

### R160 (Requirement Type)
For the case of safe radio connection with RIU's, the safe radio connection indicated to the driver shall be the one related to the current infill area.
- Section: 3.5.7.7

# Specification
- Description: Phenomena Document

## R216: [open] (Phenomena Type)
My first phenomena ...
- Synonym: [opened]

## R191 (Event-B Type)
invariant: ⊤~/openETCS/mac.bum|org.eventb.core.machineFile#mac|org.eventb.core.invariant#_AT0aAUkCEeKsg-XyRoKPGg

## R192 (Event-B Type)
event initiate_session_after_timeout  where    @grd6 l_partner ∈ terminated_ER_connectionsend~/Subset_026_comm_session/m5_safe_radio.bum|org.eventb.core.machineFile#m5_safe_radio|org.eventb.core.event#evu*

## R193 (Event-B Type)
event initiate_session_no_contact_leave_radio_hole  where    @grd6 position_radio_hole = FALSE    @grd7 signal_radio_hole = TRUEend~/Subset_026_comm_session/m4_level_changes.bum|org.eventb.core.machineFile#m4_level_changes|org.eventb.core.event#evtc

## R194 (Event-B Type)
event initiate_session_no_contact_manual_change  where    @grd6 current_level ∈ {L2, L3}    @grd7 signal_manual_change = TRUEend~/Subset_026_comm_session/m4_level_changes.bum|org.eventb.core.machineFile#m4_level_changes|org.eventb.core.event#evt\\

## R195 (Event-B Type)
event initiate_session_no_contact_mode_change  where    @grd6 current_level ∈ {L2, L3}    @grd7 signal_mode_change = TRUE    @grd8 current_status ≠ EOM  then    @act3 signal_mode_change ≔ FALSEend~/Subset_026_comm_session/m4_level_changes.bum|org.eventb.core.machineFile#m4_level_changes|org.eventb.core.event#evt[

## R196 (Event-B Type)
event receive_contact_order_non_acceptend~/Subset_026_comm_session/m4_level_changes.bum|org.eventb.core.machineFile#m4_level_changes|org.eventb.core.event#evtI

## R197 (Event-B Type)
event receive_contact_order_acceptend~/Subset_026_comm_session/m4_level_changes.bum|org.eventb.core.machineFile#m4_level_changes|org.eventb.core.event#evtH

## R198 (Event-B Type)
event initiate_session_no_contact_SOM  where    @grd6 current_status = SOM    @grd7 current_level ∈ {L2, L3}end~/Subset_026_comm_session/m4_level_changes.bum|org.eventb.core.machineFile#m4_level_changes|org.eventb.core.event#evtK

## R199 (Event-B Type)
comm_sessions~/Subset_026_comm_session/m0_basic_comm.bum|org.eventb.core.machineFile#m0_basic_comm|org.eventb.core.variable#)

## R200 (Event-B Type)
event outgoing_communciation  where    @grd3 l_partner ∈ on_trackend~/Subset_026_comm_session/m2_limit_OBU.bum|org.eventb.core.machineFile#m2_limit_OBU|org.eventb.core.event#1

## R201 (Event-B Type)
event incoming_communication  where    @grd3 l_partner ∈ on_track ∖ RIUend~/Subset_026_comm_session/m2_limit_OBU.bum|org.eventb.core.machineFile#m2_limit_OBU|org.eventb.core.event#0

## R202 (Event-B Type)
axm4: my_entity ∈ on_board~/Subset_026_comm_session/c1_entity_types.buc|org.eventb.core.contextFile#c1_entity_types|org.eventb.core.axiom#0

## R203 (Event-B Type)
event receive_contact_order_non_accept  where    @grd3 l_partner ∈ RIU ∪ (RBC ∖ (RBC ∩ accepting))  then    @act2 termination_sessions ≔ termination_sessions ∪ (RBC ∩ (incoming_sessions ∪ outgoing_sessions))end~/Subset_026_comm_session/m3_accept_system_version.bum|org.eventb.core.machineFile#m3_accept_system_version|org.eventb.core.event#evtB

## R204 (Event-B Type)
event est_perform_end_of_mission  any l_partner   where    @grd1 l_partner ∈ contacted    @grd2 l_partner ∈ establish_ER_connection    @grd3 signal_mode_change = TRUE    @grd4 current_status = EOM  then    @act1 establish_ER_connection ≔ establish_ER_connection ∖ {l_partner}end~/Subset_026_comm_session/m5_safe_radio.bum|org.eventb.core.machineFile#m5_safe_radio|org.eventb.core.event#var3

## R205 (Event-B Type)
event est_RIU_leave_L1  any l_partner   where    @grd1 l_partner ∈ contacted    @grd2 l_partner ∈ RIU    @grd3 signal_level_change = TRUE    @grd5 current_level ≠ L1    @grd4 current_status ≠ SOM  then    @act1 establish_ER_connection ≔ establish_ER_connection ∖ {l_partner}end~/Subset_026_comm_session/m5_safe_radio.bum|org.eventb.core.machineFile#m5_safe_radio|org.eventb.core.event#var6

## R206 (Event-B Type)
event est_pass_radio_hole  any l_partner   where    @grd1 l_partner ∈ contacted    @grd2 l_partner ∈ establish_ER_connection    @grd3 signal_radio_hole = TRUE ∧ position_radio_hole = TRUE    @grd4 current_status ≠ SOM  then    @act1 establish_ER_connection ≔ establish_ER_connection ∖ {l_partner}end~/Subset_026_comm_session/m5_safe_radio.bum|org.eventb.core.machineFile#m5_safe_radio|org.eventb.core.event#var5

## R207 (Event-B Type)
event est_pass_level_transition  any l_partner   where    @grd1 l_partner ∈ contacted    @grd2 l_partner ∈ establish_ER_connection    @grd3 signal_level_change = TRUE    @grd4 current_status ≠ SOM    @grd5 current_level ∈ {L0, L1, NTC}  then    @act1 establish_ER_connection ≔ establish_ER_connection ∖ {l_partner}end~/Subset_026_comm_session/m5_safe_radio.bum|org.eventb.core.machineFile#m5_safe_radio|org.eventb.core.event#var4

## R208 (Event-B Type)
event est_RBC_border  any l_partner   where    @grd1 l_partner ∈ contacted    @grd2 l_partner ∈ RBC    @grd3 signal_RBC_border = TRUE    @grd4 current_status ≠ SOM  then    @act1 establish_ER_connection ≔ establish_ER_connection ∖ {l_partner}end~/Subset_026_comm_session/m5_safe_radio.bum|org.eventb.core.machineFile#m5_safe_radio|org.eventb.core.event#var8

## R209 (Event-B Type)
event est_other_RBC_non_accept  any l_partner   where    @grd1 l_partner ∈ contacted    @grd2 l_partner ∈ RBC    @grd3 RBC ∩ accepting ∩ contacted_by ≠ ∅    @grd4 current_status ≠ SOM  then    @act1 establish_ER_connection ≔ establish_ER_connection ∖ {l_partner}end~/Subset_026_comm_session/m5_safe_radio.bum|org.eventb.core.machineFile#m5_safe_radio|org.eventb.core.event#var;

## R210 (Event-B Type)
event receive_information_incompatible  where    @grd4 l_partner ∉ system_version_compatible  then    @act2 termination_sessions ≔ termination_sessions ∪ {l_partner}end~/Subset_026_comm_session/m3_accept_system_version.bum|org.eventb.core.machineFile#m3_accept_system_version|org.eventb.core.event#evt=

## R211 (Event-B Type)
event receive_information_compatible  where    @grd4 l_partner ∈ system_version_compatibleend~/Subset_026_comm_session/m3_accept_system_version.bum|org.eventb.core.machineFile#m3_accept_system_version|org.eventb.core.event#evt6

## R212 (Event-B Type)
event establish_ER_connection_SOM  any l_partner   where    @grd1 l_partner ∈ contacted    @grd2 l_partner ∈ establish_ER_connection    @grd3 current_status = SOM  then    @act1 establish_ER_connection ≔ establish_ER_connection ∖ {l_partner}    @act2 ER_connections ≔ ER_connections ∪ {l_partner}end~/Subset_026_comm_session/m5_safe_radio.bum|org.eventb.core.machineFile#m5_safe_radio|org.eventb.core.event#evu(

## R213 (Event-B Type)
event establish_ER_connection  any l_partner   where    @grd1 l_partner ∈ contacted    @grd2 l_partner ∈ establish_ER_connection    @grd3 current_status ≠ SOM  then    @act1 establish_ER_connection ≔ establish_ER_connection ∖ {l_partner}    @act2 ER_connections ≔ ER_connections ∪ {l_partner}end~/Subset_026_comm_session/m5_safe_radio.bum|org.eventb.core.machineFile#m5_safe_radio|org.eventb.core.event#var?

## R214 (Event-B Type)
event incoming_communication  where    @grd6 l_partner ∈ ER_connectionsend~/Subset_026_comm_session/m5_safe_radio.bum|org.eventb.core.machineFile#m5_safe_radio|org.eventb.core.event#evtm

## R215 (Event-B Type)
event est_terminate_order  where    @grd2 l_partner ∈ establish_ER_connection    @grd3 current_status ≠ SOM  then    @act2 establish_ER_connection ≔ establish_ER_connection ∖ {l_partner}end~/Subset_026_comm_session/m5_safe_radio.bum|org.eventb.core.machineFile#m5_safe_radio|org.eventb.core.event#var@
