# openETCS Benchmark for Requirements Management Tools

# Specification: Specification Document
- Description: Subset-026-6 (v310)

## 6.6 (Headline Type)
On-board requirements in relation to older system versions

### 6.6.1 (Headline Type)
Introduction

#### 6.6.1.1 (Requirement Type)
This section covers the following situations:

##### 6.6.1.1.a) (Requirement Type)
Train is running on a trackside infrastructure operated with system version number X = 1

##### 6.6.1.1.b) (Requirement Type)
Train is running on a trackside infrastructure operated with system version number X = 2, but still transmitting some balise/loop/RIU information related to system version number X = 1 (see section 6.5.2).

##### 6.6.1.1.c) (Requirement Type)
Train is running on a trackside infrastructure operated with system version number X = 2, but on-board equipment has established a communication session with a neighbouring RBC certified to system version number X = 1

### 6.6.2 (Headline Type)
6.6.2 Specific requirements for on-board operating with system version number X = 1

#### R8 (Headline Type)
Exceptions to chapter 3

##### 6.6.2.1.1 (Requirement Type)
{CR719} Clause 3.12.3.4.7.2 shall be replaced with: “If the driver acknowledges before the end condition is fulfilled, the on-board equipment shall consider the driver acknowledgement as always ending the text display, regardless of the end condition defined in 3.12.3.4.3.1”.
- Trace Type -> 3.12.3.4.7.2

#### R10 (Headline Type)
Exceptions to chapter 4

##### 6.6.2.1.8 (Requirement Type)
Void

#### R12 (Headline Type)
Exceptions to chapter 5

##### 6.6.2.1.9 (Requirement Type)
Void

#### R14 (Headline Type)
Exceptions to chapter 7, 8

##### 6.6.2.1.10 (Requirement Type)
Void

### 6.6.3 (Headline Type)
6.6.3 Handling of air gap data related to system version number X = 1

#### R19 (Headline Type)
General

##### 6.6.3.1.1 (Requirement Type)
For information received from trackside, the message consistency check shall be achieved taking into account the exceptions to chapters 7 and 8, as described in sections  and 6.5.1.2.

##### 6.6.3.1.2 (Requirement Type)
For information received from trackside, the ERTMS/ETCS on-board equipment shall use the translation tables defined here below, in order to use the information as if it had been elaborated in compliance with the current chapters 7 and 8.

#### R20 (Headline Type)
Packets received from balise, loop, RIU, RBC

##### 6.6.3.1.3 (Requirement Type)
In the table below, the translation of information may depend on the on-board operated system version at the time the information is received and accepted on-board.

##### 6.6.3.1.4 (Requirement Type)
When a level transition or an RBC/RBC handover is announced, the information stored on-board in the transition buffer shall be translated according to system version operated on-board at the time the information is released from the transition buffer (i.e. the system version operated by the trackside infrastructure, towards which the train is running).

##### 6.6.3.1.5 (Requirement Type)
Depending on the packet, the action can be:

###### 6.6.3.1.5.a) (Requirement Type)
data is unchanged,

###### 6.6.3.1.5.b) (Requirement Type)
data is rejected,

###### 6.6.3.1.5.c) (Requirement Type)
data is translated,

###### 6.6.3.1.5.d) (Requirement Type)
not relevant

##### R29 (Headline Type)
Packet Action Table

###### 45 (Packet Action Type)
Radio Network registration
- OS System Version Number X=1: U = Unchanged
- OS System Version Number X=2: U = Unchanged

###### 46 (Packet Action Type)
Conditional Level Transition Order
- OS System Version Number X=1: U = Unchanged
- OS System Version Number X=2: U = Unchanged

###### 49 (Packet Action Type)
List of balises for SH Area
- OS System Version Number X=1: U = Unchanged
- OS System Version Number X=2: U = Unchanged

###### 51 (Packet Action Type)
Axle load Speed Profile
- OS System Version Number X=1: T = Translated
- OS System Version Number X=2: T = Translated
- links to -> [4]
- links to -> [5]

###### 57 (Packet Action Type)
Movement Authority Request Parameters
- OS System Version Number X=1: U = Unchanged
- OS System Version Number X=2: U = Unchanged

###### 58 (Packet Action Type)
Position Report Parameters
- OS System Version Number X=1: U = Unchanged
- OS System Version Number X=2: U = Unchanged

###### 63 (Packet Action Type)
List of Balises in SR Authority
- OS System Version Number X=2: U = Unchanged
- OS System Version Number X=1: U = Unchanged

###### 65 (Packet Action Type)
Temporary Speed Restriction
- OS System Version Number X=2: U = Unchanged
- OS System Version Number X=1: U = Unchanged

###### 66 (Packet Action Type)
Temporary Speed Restriction Revocation
- OS System Version Number X=1: U = Unchanged
- OS System Version Number X=2: U = Unchanged

###### 67 (Packet Action Type)
Track Condition Big Metal Masses
- OS System Version Number X=2: U = Unchanged
- OS System Version Number X=1: U = Unchanged

###### 68 (Packet Action Type)
Track Condition
- OS System Version Number X=1: U = Unchanged
- OS System Version Number X=2: U = Unchanged

###### 70 (Packet Action Type)
Route Suitability Data
- OS System Version Number X=1: U = Unchanged
- OS System Version Number X=2: U = Unchanged

###### 71 (Packet Action Type)
Adhesion Factor
- OS System Version Number X=1: U = Unchanged
- OS System Version Number X=2: U = Unchanged

###### 72 (Packet Action Type)
Packet for sending plain text messages
- OS System Version Number X=1: U = Unchanged
- OS System Version Number X=2: U = Unchanged

##### R43 (Headline Type)
Package Action Table Footnotes

###### [4] (Requirement Type)
If Q_TRACKINIT = 1, D_TRACKINIT (introduced in system version number X = 2) shall be set to 0

###### [5] (Requirement Type)
The variable M_AXLELOAD (modified in system version number X = 2) shall be set according to the following table:

###### Translated value on-board (Requirement Type)
Value received from X = 1 trackside

###### A (Requirement Type)
M_AXLELOAD < 18 t

###### B1 (Requirement Type)
18 t ≤ M_AXLELOAD < 20 t

###### C2 (Requirement Type)
20 t ≤ M_AXLELOAD < 22,5 t

###### D2 (Requirement Type)
22,5 t ≤ M_AXLELOAD < 25 t

###### E4 (Requirement Type)
25 t ≤ M_AXLELOAD ≤ 40 t
or M_AXLELOAD = “Axle load above 40 t”

# Specification
- Description: Subset-026-3 (v310)

## 3.12.3.4 (Rich Requirement Type)
Conditions for Start/End of Indication

### 3.12.3.4.1 (Rich Requirement Type)
It shall be possible to specify individual events for start/end condition of indication.

### 3.12.3.4.2 (Rich Requirement Type)
The following events can be used to define the start condition:
- Location
- Mode (start display as soon as in mode)
- Level (start display as soon as in level)

### 3.12.3.4.3 (Rich Requirement Type)
The following events can be used to define the end condition:
- Location
- Time
- Mode (stop display when leaving mode)
- Level (stop display when leaving level)

#### 3.12.3.4.3.1 (Rich Requirement Type)
It shall be possible to define whether one or all of the events used from the referenced lists in 3.12.3.4.2/3.12.3.4.3 have to be fulfilled to define the start/end condition. This definition shall apply to both start and end conditions.
- links to -> 3.12.3.4.2
- links to -> 3.12.3.4.3

#### 3.12.3.4.3.2 (Rich Requirement Type)
In case a confirmation of the text message is requested, it shall be possible to define whether the driver acknowledgement is considered:
a) As always ending the text display, regardless of the end condition defined in the linked requirement 3.12.3.4.3.1
b) As a necessary condition to end the text display, in addition to the end condition defined in the linked requirement 3.12.3.4.3.1.
- links to -> 3.12.3.4.3.1

### 3.12.3.4.4 (Rich Requirement Type)
The end condition shall be evaluated as soon as the start condition is fulfilled. No display shall take place if the end condition is immediately fulfilled.

### 3.12.3.4.5 (Rich Requirement Type)
Once the text message is displayed and the end condition is fulfilled, the start condition shall not be re-evaluated.

### 3.12.3.4.6 (Rich Requirement Type)
When the end event "location" is used, the length on which the text is displayed shall refer to the location used for the start condition, independently from other start events.

### 3.12.3.4.7 (Rich Requirement Type)
In case a confirmation of the text message is requested, it shall be possible to define whether the service brake or emergency brake application shall be commanded if the driver does not acknowledge before the end condition is fulfilled..

#### 3.12.3.4.7.1 (Rich Requirement Type)
If the driver does not acknowledge before the end condition is fulfilled, the text message shall remain displayed until acknowledged by driver.

#### 3.12.3.4.7.2 (Rich Requirement Type)
If the driver acknowledges before the end condition is fulfilled, the on-board equipment shall consider the driver acknowledgement as always ending the text display, regardless of the end condition defined in 3.12.3.4.3.1
